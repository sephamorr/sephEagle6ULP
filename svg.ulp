#usage "<b>Eagle schematic exporting tool  version 1.0 </b>\n"
       "<p>"
       "This ULP can convert an Eagle CAD schematics into SVG files."
       "<p>"
       "Load any schematic and execute the ULP in the eagle."
       "<p>"
       "<author>Author: nils.springob (at) nicai-systems.de</author>"
       "based on eagle2ps by juergen.messerer (at) freesurf.ch"
       
real VERSION   = 1.0;

/*
 * CHANGELOG================================================
 *
 * 1.0 (16.04.2008): Some bugfixes      
 * 0.2 (11.04.2008): Using CSS for layer-styles      
 * 0.1 (08.03.2008): Initial version    
 *
 */  

/* ==========================================================================
 * License: This file is released under the license of the GNU Public license
 *          Version 2.
 * ==========================================================================*/   
 

int true  = 1;
int false = 0;

int minimum( int x1, int x2 ) {
   if( x1 < x2 )
      return x1;
   else
      return x2;
}

int maximum( int x1, int x2 ) {
   if( x1 > x2 )
      return x1;
   else
      return x2;
}

int g_monochrome = 0;

string htmlcolor(int col) {
  string result;
  sprintf(result, "#%06x", col);
  return result;
}

//------------------------------------------------------
// replace xml reserved chars and build 2-byte utf-8 characters  
//------------------------------------------------------

string encodeText(string strText) {
  string newText = "";
  int i=0;
  
  while (strText[i]) {
    char c = strText[i++];
    switch(c) {
      case '<': newText += "&lt;"; break; 
      case '>': newText += "&gt;"; break;
      case '&': newText += "&amp;"; break;
      default:
        if (c>=0xc0) {
          newText += char(0xc3);
          newText += char(c-0x40);
        } else if (c>=0x80) {
          newText += char(0xc2);
          newText += char(c);
        } else {
          newText += c;
        }
    }
  }
  return newText;
}

//------------------------------------------------------
// SVG output functions
//------------------------------------------------------

string svgLineStyle(int width, int cap) {
  string lineCap="round";

  switch (cap) {
    case CAP_FLAT: lineCap = "butt"; break;
    case CAP_ROUND: lineCap = "round"; break;
    default: lineCap = "round"; break;
  }

  string style;
  sprintf(style, "stroke-width:%f; stroke-linecap:%s",
    u2mm(width), lineCap);
  return style;    
}

void svgWriteLine(int x1, int y1, int x2, int y2, int layer, string style) {
  printf("<line class='l%d' x1='%f' y1='%f' x2='%f' y2='%f' style='%s'/>\n",
    layer,
    u2mm(x1), u2mm(-y1), 
    u2mm(x2), u2mm(-y2),
    style);
}

void svgWriteArc(int x1, int y1, int x2, int y2, int radius, char longpath, int layer, string style) {
  printf("<path class='l%d' d='M %f,%f A %f,%f,0,%c,0,%f,%f' style='%s'/>\n",
    layer,
    u2mm(x1), u2mm(y1),
    u2mm(radius), u2mm(radius),
    longpath,
    u2mm(x2), u2mm(y2),
    style);
}

void svgWriteRect(int x1, int y1, int x2, int y2, real angle, int layer) {
  string rotation="";

  if (angle!=0.0) {
    sprintf(rotation, " transform='rotate(%f,%f,%f)'",
      -angle, 
      u2mm(x1+x2)/2.0, u2mm(-y1-y2)/2.0);
  }   
  printf("<rect class='l%d' x='%f' y='%f' width='%f' height='%f'%s/>\n",
    layer,
    u2mm(x1), u2mm(-y2), 
    u2mm(x2-x1), u2mm(y2-y1),
    rotation);
}

void svgWriteCircle(int x, int y, int radius, int lwidth, int layer) {
   printf("<circle class='l%d' cx='%f' cy='%f' r='%f' style='stroke-width:%f'/>\n", 
     layer,
     u2mm(x), u2mm(-y),
     u2mm(radius), 
     u2mm(lwidth));
}

void svgWriteDot(int x, int y, int diameter, int layer) {
   printf("<circle class='j%d' cx='%f' cy='%f' r='%f'/>\n", 
     layer,
     u2mm(x), u2mm(-y),
     u2mm(diameter)/2.0);
}


void svgWritePathStart(int layer, string style) {
  printf( "<path class='l%d' style='%s' d='", layer, style);
}

void svgWritePathSegment(int x1, int y1, int x2, int y2) {
  printf( " M %f,%f L %f,%f", u2mm(x1), u2mm(-y1), u2mm(x2), u2mm(-y2));    
}

void svgWritePathEnd() {
  printf( "'/>\n");
}



void svgWriteText(int x, int y, real angle, char align, string text, int size, int layer) {
  string style;
  sprintf(style, "font-size:%fpt;", u2mm(size)*1.1);

  if (align=='e') {
    style += " text-anchor:end;";
  }

  if (angle==0.0) {
    printf( "<text class='l%d' x='%f' y='%f' style='%s'>%s</text>\n",
      layer,
      u2mm(x), u2mm(-y), 
      style, 
      text);
  
  } else {
    printf( "<text class='l%d' x='0' y='0' style='%s' transform='translate(%f, %f) rotate(%f)'>%s</text>\n",
      layer,
      style,
      u2mm(x), u2mm(-y), 
      angle,
      text);  
  }
}



//------------------------------------------------------
// write piece
//------------------------------------------------------
void write_piece(UL_WIRE W) {
  string style = svgLineStyle(W.width, W.cap);
      
  if (W.arc) {
    char longpath;
    if( W.arc.angle1 < W.arc.angle2 ) {
      longpath='0';
    } else {
      longpath='1';
    }
    svgWriteArc(W.arc.x1, W.arc.y1, W.arc.x2, W.arc.y2, W.arc.radius, longpath, W.layer, style);
  } else {
    svgWriteLine(W.x1, W.y1, W.x2, W.y2, W.layer, style);
  }
}


//------------------------------------------------------
// writing general wires
//------------------------------------------------------
void write_wires(UL_WIRE W) {
   
  if ( W.style == WIRE_STYLE_LONGDASH || W.style == WIRE_STYLE_SHORTDASH || W.style == WIRE_STYLE_DASHDOT ) {
    W.pieces(P) {
      write_piece(P);           
    }      
  } else if (W.arc) {
    string style = svgLineStyle(W.arc.width, W.cap);
    char longpath;
    if( W.arc.angle1 < W.arc.angle2 ) {
      longpath='0';
    } else {
      longpath='1';
    }
    svgWriteArc(W.arc.x1, W.arc.y1, W.arc.x2, W.arc.y2, W.arc.radius, longpath, W.layer, style);   
  } else {
    string style = svgLineStyle(W.width, W.cap);
    svgWriteLine(W.x1, W.y1, W.x2, W.y2, W.layer, style);
  }
}


//------------------------------------------------------
// writing general rectangles
//------------------------------------------------------
void write_rectangles(UL_RECTANGLE R) {
  svgWriteRect(R.x1, R.y1, R.x2, R.y2, R.angle, R.layer);
}



//------------------------------------------------------
// writing vector texts
//------------------------------------------------------
void write_vector_text(UL_TEXT T) {
  int cnt=0;
  T.wires(W) {
    string lineCap;
    if (cnt==0) {
      string style = svgLineStyle(W.width, W.cap);
      svgWritePathStart(W.layer, style);
    }
    svgWritePathSegment(W.x1, W.y1, W.x2, W.y2);
    cnt++;
  }
  if (cnt>0) {
    svgWritePathEnd();
  }
}

//------------------------------------------------------
// writing proportional texts
//------------------------------------------------------
void write_prop_text(UL_TEXT T) {
  string newText = encodeText(T.value);
   
  int posX = T.x;
  int posY = T.y;   
  int textAngle = T.angle;
  int textSize = T.size;
  
  char hmode, vmode, rmode;
   
  if( T.mirror > 0 ) {
    switch( textAngle ) {
      case 0:   vmode='e'; hmode='b'; rmode='0'; break;
      case 90:  vmode='b'; hmode='t'; rmode='9'; break;
      case 180: vmode='b'; hmode='t'; rmode='0'; break;
      case 270: vmode='e'; hmode='b'; rmode='9'; break;
    } 
  } else {
    switch( textAngle ) {
      case 0:   vmode='b'; hmode='b'; rmode='0'; break;
      case 90:  vmode='b'; hmode='b'; rmode='9'; break;
      case 180: vmode='e'; hmode='t'; rmode='0'; break;
      case 270: vmode='e'; hmode='t'; rmode='9'; break;
    } 
  }

  if (rmode=='0') {
    if (hmode=='t') {
      posY -= textSize;
    }
    svgWriteText(posX, posY, 0.0, vmode, newText, textSize, T.layer);
  } else {
    if (hmode=='t') {
      posX += textSize;
    }
    svgWriteText(posX, posY, -90.0, vmode, newText, textSize, T.layer);
  }
}


//------------------------------------------------------
// writing general texts
//------------------------------------------------------
void write_text(UL_TEXT T) {
  if (T.font==FONT_VECTOR) {
    write_vector_text(T);
  } else {
    write_prop_text(T);
  }
}



//------------------------------------------------------
// writing general circles
//------------------------------------------------------
void write_circles(UL_CIRCLE C) {
  svgWriteCircle(C.x, C.y, C.radius, C.width, C.layer);
}


//------------------------------------------------------
// writing elements of the busses for a sheet
//------------------------------------------------------
void write_segments(UL_SEGMENT SEG) {
   string color = "#000000";
   int layer = 0;      
   SEG.wires(W) 
   {
      layer = W.layer;      
      write_wires(W);
   }
         
   SEG.junctions(J)
   {  
     svgWriteDot(J.x, J.y, J.diameter, layer);
   }

   SEG.texts(T)
   {
      write_text(T);
   }
}


//------------------------------------------------------
// write general polygons
//------------------------------------------------------
void write_polygons(UL_POLYGON P) {
  int count = 0;
  printf( "<polygon class='l%d' points='", P.layer);

  P.wires(W) {
    if (count == 0) {
      printf( "%f %f", u2mm(W.x1), u2mm(-W.y1)); 
    } else {
      printf( ", %f %f", u2mm(W.x1), u2mm(-W.y1));
    }
    ++count;
  }

  printf( "'/>\n" );

}

//------------------------------------------------------
// writing elements of the busses for a sheet
//------------------------------------------------------
void write_sheet_busses(UL_SHEET SH) {
   SH.busses(B) {
      printf("<g><title>BUS %s</title>\n", encodeText(B.name));
      B.segments(SEG) {
         write_segments(SEG);
      }
      printf("</g>\n");
   }
}

//------------------------------------------------------
// writing elements of the nets for a sheet
//------------------------------------------------------
void write_sheet_nets(UL_SHEET SH) {
   SH.nets(N) {
      printf("<g><title>NET %s</title>\n", encodeText(N.name));
      N.segments(SEG) {
         write_segments(SEG);
      }
      printf("</g>\n");
   }
}

//------------------------------------------------------
// writing elements of the polygons for a sheet
//------------------------------------------------------
void write_sheet_polygons(UL_SHEET SH) {
   SH.polygons(P) {
      write_polygons(P);
   }
}

//------------------------------------------------------
// writing elements of the rectangles for a sheet
//------------------------------------------------------
void write_sheet_rectangles(UL_SHEET SH) {
   SH.rectangles(R) {
      write_rectangles(R);
   }
}

//------------------------------------------------------
// writing elements of the circles for a sheet
//------------------------------------------------------
void write_sheet_circles(UL_SHEET SH) {
   SH.circles(C) {
      write_circles(C);
   }
}

//------------------------------------------------------
//write the text items of a sheet
//------------------------------------------------------
void write_sheet_texts(UL_SHEET SH) {
   SH.texts(T) {
      write_text(T);
   }
}

//------------------------------------------------------
//write the parts of a sheet
//------------------------------------------------------
void write_sheet_parts(UL_SHEET SH) {
  SH.parts(P) {
    P.instances(I) {
      printf("<g><title>PART %s</title>\n", encodeText(I.name));
      I.gate.symbol.polygons(P) {
        write_polygons(P);
      }
         
      I.gate.symbol.circles(C) {
        write_circles(C);
      }
         
      I.gate.symbol.rectangles(R) {
        write_rectangles(R);
      }
         
      I.gate.symbol.pins(P) {
        P.wires(W) {
          write_wires(W);
        }
            
        P.circles(C) {
          write_circles(C);
        }
            
        P.texts(T) {
          write_text(T);
        }
      }
         
      I.gate.symbol.wires(W) {
        write_wires(W);
      }
         
      I.gate.symbol.texts(T) {
        write_text(T);
      }
         
      I.texts(T) {
        write_text(T);
      }
      printf("</g>\n");      
    }
  }
}

//------------------------------------------------------
//write the text items of a sheet
//------------------------------------------------------
void write_sheet_wires (UL_SHEET SH) {
   SH.wires(W)
   {
      write_wires(W);
   }
}


void write_svg_layerStyle (UL_LAYER L) {
  string color;
  if (g_monochrome) {
    color = htmlcolor(0);
  } else {
    color = htmlcolor(palette(L.color)&0x00ffffff);
  }
  
  printf ("path.l%d {stroke:%s; fill:none; }\n", L.number, color);
  printf ("line.l%d {stroke:%s; fill:none; }\n", L.number, color);
  printf ("circle.l%d {stroke:%s; fill:none; }\n", L.number, color);
  printf ("circle.j%d {fill:%s; }\n", L.number, color);
  printf ("rect.l%d {fill:%s; }\n", L.number, color);
  printf ("text.l%d {font-family:sans-serif; fill:%s; }\n", L.number, color);
  printf ("polygon.l%d {fill:%s; }\n", L.number, color);
}


void write_svg_styles() {
  printf ("<defs>\n");
  printf ("<style type='text/css'>\n");
  printf ("<![CDATA[\n");
  schematic(SCH) {
    SCH.layers(L) {
      write_svg_layerStyle(L);
    }
  }
  printf ("]]>\n");
  printf ("</style>\n");
  printf ("</defs>\n");
}


                                         
//------------------------------------------------------
//write svg header
//------------------------------------------------------
void write_svg_header(UL_SHEET SH) {
  int t = time();
  int pageCount = 0;
  string header =  "<?xml version=\"1.0\" encoding=\"UTF-8\"?>\n";
  header += "<svg xmlns='http://www.w3.org/2000/svg' xmlns:xlink='http://www.w3.org/1999/xlink' version='1.1' ";
  header += "width='%fmm' height='%fmm' viewBox='%f %f %f %f'>\n";

  int dimX    = SH.area.x2-SH.area.x1;
  int dimY    = SH.area.y2-SH.area.y1;
  printf(header, u2mm(dimX), u2mm(dimY), u2mm(SH.area.x1), u2mm(-SH.area.y2), u2mm(dimX), u2mm(dimY));

  schematic(SCH) {
    printf("<title>%s - sheet %d</title>\n", encodeText(SCH.name), SH.number);
    printf("<desc>generated by eagle2svg, developed by http://www.nicai-systems.de</desc>\n");
  }

  write_svg_styles();
  printf ("<g id='surface0'>\n");
}


//------------------------------------------------------
//write svg footer
//------------------------------------------------------
void write_svg_footer(UL_SHEET SH) {
  string footer =  "</g>\n";
  footer += "</svg>\n";
  printf(footer);
}


//------------------------------------------------------
//write whole sheet 
//------------------------------------------------------
void write_svg_sheet(string fileName) {
  output(fileName, "Fwt") {
    if(sheet) {
      sheet(SH) {
        write_svg_header(SH);
        write_sheet_texts(SH);
        write_sheet_wires(SH);
        write_sheet_nets(SH);
        write_sheet_busses(SH);
        write_sheet_rectangles(SH);
        write_sheet_polygons(SH);
        write_sheet_circles(SH);
        write_sheet_parts(SH);
        write_svg_footer(SH);
      }
    }  
  }   
}


//------------------------------------------------------
// Global mod_ and lib_name
//------------------------------------------------------
string sch_name ;   


//------------------------------------------------------
// Select the path where the schematic will be saved 
//------------------------------------------------------
void openSchematicPath(string startPath) {
   string dirName = "";
   string stringArray[];
   dirName = dlgDirectory("Select a directory", startPath);
   
   if( dirName != "" ) {
      schematic(S) {
         int n = 0;
         string tmpName = S.name; 
         int nr = strsplit(stringArray, tmpName, '/');
         sch_name = dirName + "/" + stringArray[nr-1];
         sch_name = strsub(sch_name , 0, strlen(sch_name) - 4) + ".ps";
      }
   }
}

int displayDialog(string titleStr) {
  int space = 10;
  int result = dlgDialog(titleStr) {
    dlgVBoxLayout {
      dlgVBoxLayout {

        dlgHBoxLayout dlgSpacing(500);
        dlgStretch(0);
        dlgSpacing(space);
        dlgLabel("Export to file:");
        dlgStretch(0);
        dlgHBoxLayout {
          dlgSpacing(space);
          dlgStringEdit(sch_name);
          dlgSpacing(space);
          dlgPushButton("...") openSchematicPath("C:\\");
          dlgSpacing(space);
        }
        dlgCheckBox("Monochrome", g_monochrome);
        dlgStretch(10);
        dlgLabel("developed by <a href='http://www.nicai-systems.de'>http://nibo.nicai-systems.de</a>, based on eagle2ps");
      }
      dlgStretch(0);
      dlgHBoxLayout {
        dlgStretch(1);
        dlgPushButton("+OK") dlgAccept();
        dlgSpacing(space);
        dlgPushButton("-Cancel") dlgReject();
        dlgStretch(0);
        dlgSpacing(space);
      }
      dlgStretch(10);
    }
  };
  return result;
}


//------------------------------------------------------
// main program 
//------------------------------------------------------
  int result;
  string ref;
  string titleStr;

  sprintf(titleStr, "Export Eagle sheet to SVG, Version: %.1f", VERSION);

  if (schematic) {
    schematic(S) {
      sheet(SH) {
        sprintf(sch_name, "%s_p%d.svg", strsub(S.name, 0, strlen(S.name) - 4), SH.number);
      }
    }
  } else {
    dlgMessageBox("Please run from schematic editor." ); 
    exit(EXIT_FAILURE);
  }

  result = displayDialog(titleStr); 

  if(result) {
    write_svg_sheet(sch_name);
  } else { 
    //dlgMessageBox("Canceled!" ); 
  }
  exit(EXIT_SUCCESS);
